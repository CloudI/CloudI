--
-- BSD LICENSE
-- 
-- Copyright (c) 2009, Michael Truog
-- All rights reserved.
-- 
-- Redistribution and use in source and binary forms, with or without
-- modification, are permitted provided that the following conditions are met:
-- 
--     * Redistributions of source code must retain the above copyright
--       notice, this list of conditions and the following disclaimer.
--     * Redistributions in binary form must reproduce the above copyright
--       notice, this list of conditions and the following disclaimer in
--       the documentation and/or other materials provided with the
--       distribution.
--     * All advertising materials mentioning features or use of this
--       software must display the following acknowledgment:
--         This product includes software developed by Michael Truog
--     * The name of the author may not be used to endorse or promote
--       products derived from this software without specific prior
--       written permission
-- 
-- THIS SOFTWARE IS PROVIDED BY THE COPYRIGHT HOLDERS AND
-- CONTRIBUTORS "AS IS" AND ANY EXPRESS OR IMPLIED WARRANTIES,
-- INCLUDING, BUT NOT LIMITED TO, THE IMPLIED WARRANTIES
-- OF MERCHANTABILITY AND FITNESS FOR A PARTICULAR PURPOSE ARE
-- DISCLAIMED. IN NO EVENT SHALL THE COPYRIGHT OWNER OR
-- CONTRIBUTORS BE LIABLE FOR ANY DIRECT, INDIRECT, INCIDENTAL,
-- SPECIAL, EXEMPLARY, OR CONSEQUENTIAL DAMAGES (INCLUDING,
-- BUT NOT LIMITED TO, PROCUREMENT OF SUBSTITUTE GOODS OR
-- SERVICES; LOSS OF USE, DATA, OR PROFITS; OR BUSINESS
-- INTERRUPTION) HOWEVER CAUSED AND ON ANY THEORY OF LIABILITY,
-- WHETHER IN CONTRACT, STRICT LIABILITY, OR TORT (INCLUDING
-- NEGLIGENCE OR OTHERWISE) ARISING IN ANY WAY OUT OF THE USE
-- OF THIS SOFTWARE, EVEN IF ADVISED OF THE POSSIBILITY OF SUCH
-- DAMAGE.
--
WorkerProtocol DEFINITIONS IMPLICIT TAGS ::=
BEGIN
EXPORTS WorkerMessage;

-- relevant Erlang asn1 documentation:
-- http://erlang.org/doc/apps/asn1/ref_man_frame.html
-- http://erlang.org/doc/apps/asn1/part_frame.html

-- the system handles generic work, described by the work title (job).
-- a specific type of work (work title, or job) has many tasks.
-- certain workers can do certain jobs (work titles), so the worker
-- receives tasks when they pull tasks for a particular type of work.

WorkerMessage ::= [PRIVATE 0] CHOICE {

    -- worker sends a request for a task to an Erlang node
    pullJobTaskRequest           [PRIVATE 1] SEQUENCE {
        workerName     IA5String,
        workTitle      IA5String,
        id             INTEGER (0..4294967295)
    },
    -- an Erlang node responds to a request for work from a worker
    pullJobTaskResponse          [PRIVATE 2] SEQUENCE {
        workTitle      IA5String,
        id             INTEGER (0..4294967295),
        totalIds       INTEGER (0..4294967295),
        sequence       INTEGER (0..4294967295),
        taskSize       OCTET STRING, -- double floating-point number < 1.0
        taskData       OCTET STRING, -- if empty, no work available
        queries        Queries,
        failureCount   INTEGER (0..4294967295)
    },
    -- worker sends the result of a task to an Erlang node
    pushJobTaskResultRequest     [PRIVATE 3] SEQUENCE {
        workerName     IA5String,
        workTitle      IA5String,
        id             INTEGER (0..4294967295),
        sequence       INTEGER (0..4294967295),
        taskSize       OCTET STRING, -- double floating-point number < 1.0
        taskData       OCTET STRING, -- binary data
        elapsedTime    OCTET STRING, -- double floating-point number (in hours)
        returnValue    BOOLEAN,
        queries        Queries,
        failureCount   INTEGER (0..4294967295)
    },
    -- an Erlang node responds once the results are safely stored
    pushJobTaskResultResponse    [PRIVATE 4] SEQUENCE {
        workTitle      IA5String,
        id             INTEGER (0..4294967295),
        taskData       OCTET STRING -- binary data
    }
}

Queries ::= [PRIVATE 5] SEQUENCE OF Query

Query ::= [PRIVATE 6] SEQUENCE {
    type IA5String,
    query UTF8String -- UTF8 or binary data
}

END
